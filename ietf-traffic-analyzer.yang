module ietf-traffic-analyzer {
  yang-version 1.1;
  namespace "urn:ietf:params:xml:ns:yang:ietf-traffic-analyzer";
  prefix ntta;

  import ietf-interfaces {
    prefix if;
    reference
      "RFC 8343: A YANG Data Model for Interface Management";
  }
  import ietf-yang-types {
    prefix yang;
    reference
      "RFC 9911: Common YANG Data Types";
  }
  import ietf-netconf-acm {
    prefix nacm;
    reference
      "RFC 8341: Network Configuration Access Control Model";
  }

  organization
    "IETF Benchmarking Methodology Working Group";
  contact
    "WG Web:   <https://datatracker.ietf.org/group/bmwg/about/>
     WG List:  BMWG <mailto:bmwg@ietf.org>

     Author:   Vladimir Vassilev
               <mailto:vladimir@lightside-instruments.com>";
  description
    "This module contains a collection of YANG definitions for
     management of the traffic analyzer functionality part
     of network interconnect testers.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-06-26 {
    description
      "Initial revision.";
    reference
      "RFC XXXX: A YANG Data Model for
                 Network Tester Management";
  }

  feature testframe-filter {
    description
      "Indicates that the device implements
       a filter that can specify a subset of packets to be
       analyzed as testframes.";
  }

  feature capture-filter {
    description
      "Indicates that the device implements
       a filter that can specify a subset of packets to be
       captured.";
  }

  feature idle-octets-counter {
    description
      "Indicates that the device implements
       idle-octets counter that accumulates the time
       the link is not utilized. The minimum required
       idle gaps are not counted as idle octets.";
  }

  feature capture {
    description
      "Indicates that the device implements
       packet capture functionality.";
  }

  identity testframe-type {
    description
      "Base identity for all test frame types.";
  }

  identity unspecified {
    base testframe-type;
    description
      "The configuration of the testframe
       type of the traffic analyzer is done outside of
       the data model specified configuration interface.";
  }

  identity testframe-filter {
    description
      "Base testframe-filter identity.";
  }

  identity capture-filter {
    description
      "Base capture-filter identity.";
  }

  identity bit-field-match {
    base ntta:testframe-filter;
    description
      "Bit field matching filter. Frames that do not have
       equal values for all the bits of the specified data
       at the offsets specified with bits set in the mask
       are not processed as test frames.";
  }

  grouping statistics-data {
    description
      "Analyzed traffic statistics and test frame statistics.";
    container statistics {
      description
        "A collection of interface-related statistics objects.
         The counters in this container must be initialized
         to zero when the traffic-analyzer container is created";
      leaf pkts {
        type yang:counter64;
        description
          "Total count of packets analyzed.";
      }
      leaf octets {
        type yang:counter64;
        description
          "Total count of octets analyzed.";
      }
      leaf idle-octets {
        if-feature "idle-octets-counter";
        type yang:counter64;
        description
          "Total accumulated period with no frame transmission
           taking place measured in octets at the current link
           speed. This counter increments whenever the interface
           is not operating at 100% of its capacity.

           Octets not counted in '../octets' but not idle are,
           for example, layer 1 framing octets - for Ethernet interfaces
           7+1 preamble octets per packet as well as the 12-octets
           minimum gap.";
      }
      leaf errors {
        type yang:counter64;
        description
          "Count of packets with errors.
           Not counted in the pkts or captured.
           For example packets with CRC error.";
      }
    }
    container testframe-statistics {
      description
        "Statistics for received testframes containing
         either sequence number, payload checksum,
         timestamp or any combination of these features.";
      leaf pkts {
        type yang:counter64;
        description
          "Total count of testframes.";
      }
      leaf octets {
        type yang:counter64;
        description
          "Total count of testframe octets.";
      }
      leaf sequence-errors {
        type yang:counter64;
        description
          "Total count of testframes with
           unexpected sequence number. After each sequence
           error the expected next sequence number is
           updated.";
      }
      leaf payload-errors {
        type yang:counter64;
        description
          "Total count of testframes with
           payload errors.";
      }
      container latency {
        description
          "Latency statistics.";
        leaf samples {
          type uint64;
          description
            "Total count of testframes used for estimating
             the latency statistics. When every testframe is
             used, samples='../pkts'.";
        }
        leaf min {
          type uint64;
          units "nanoseconds";
          description
            "Minimum measured latency.";
        }
        leaf max {
          type uint64;
          units "nanoseconds";
          description
            "Maximum measured latency.";
        }
        leaf average {
          type uint64;
          units "nanoseconds";
          description
            "The sum of all sampled latencies divided
             by the number of samples.";
        }
        leaf latest {
          type uint64;
          units "nanoseconds";
          description
            "Latency of the latest sample.";
        }
      }
      container last-sequence-error {
        description
          "Last sequence error state data.";
        leaf timestamp {
          type yang:date-and-time;
          description
            "Timestamp of the moment a testframe with
             unexpected sequence number was received.";
        }
        leaf expected {
          type uint64;
          description
            "Expected sequence number.";
        }
        leaf received {
          type uint64;
          description
            "Received sequence number.";
        }
      }
    }
  }

  grouping capture-statistics-data {
    description
      "Capture process statistics.";
    container statistics {
      description
        "Statistics for captured frames.";
      leaf pkts {
        type yang:counter64;
        description
          "Total count of captured frames.";
      }
      leaf octets {
        type yang:counter64;
        description
          "Total count of captured octets.";
      }
    }
  }

  grouping capture-config-data {
    description
      "Grouping with a capture configuration container.";
    container capture {
      if-feature "capture";
      presence "Enables the capture functionality";
      description
        "Contains capture parameters.";
      leaf max-frames-visible {
        type uint64;
        description
          "Maximum number of frame entries available in
           the state/capture/frames container.";
      }
      leaf max-frame-data-visible {
        type uint32;
        description
          "Maximum length of data per frame available in
           the state/capture/frames/frame/data.";
      }
      container start-trigger {
        presence "Enables trigger condition that starts
                  the capture process.";
        description
          "Specifies when the capture start is triggered.";
        choice start-trigger {
          mandatory true;
          description
            "Choice of start-trigger condition.";
          case frame-index {
            description
              "Start capturing frames at the specified frame index.";
            leaf frame-index {
              type uint64;
              description
                "First captured frame index.";
            }
          }
          case testframe-index {
            description
              "Start capturing frames at the specified
               testframe index.";
            leaf testframe-index {
              type uint64;
              description
                "First captured testframe index.";
            }
          }
        }
      }
      container stop-trigger {
        presence "Enables trigger condition that stops
                  the capture process.";
        description
          "Specifies when the capture is stopped.";
        choice stop-trigger {
          mandatory true;
          description
            "Choice of stop-trigger condition.";
          case when-full {
            description
              "Stops capturing when the implementation can not store
               more frames.";
            leaf when-full {
              type empty;
              description
                "When present in configuration capture stops when
                 the capture buffer is full.";
            }
          }
        }
      }
      container filter {
        if-feature "capture-filter";
        presence "When packets are filtered before captured
                  according to the filter type";
        description
          "Contains the filtering rules for capturing only
           a specific subset of the frames.";
        leaf type {
          type identityref {
            base ntta:capture-filter;
          }
          mandatory true;
          description
            "Type of the applied filter. External modules can
             define alternative filter type identities.";
        }
      }
    }
  }

  grouping capture-data {
    description
      "Grouping with statistics and data of one or more
       captured frames.";
    container capture {
      if-feature "capture";
      description
        "Capture statistics data and frames.";
      uses capture-statistics-data;
      container frames {
        description
          "Contains list of captured frames.";
        list frame {
          key "sequence-number";
          description
            "Statistics and data of a captured frame.";
          leaf sequence-number {
            type uint64;
            description
              "Incremental counter of frames captured.";
          }
          leaf timestamp {
            type yang:date-and-time;
            description
              "Timestamp of the moment the frame was captured.";
          }
          leaf size {
            type uint32;
            description
              "Frame length. Ideally the data captured will be
               of the same length but can be shorter
               depending on implementation limitations.";
          }
          leaf data {
            type binary;
            description
              "Raw data of the captured frame.";
            nacm:default-deny-all;
          }
        }
      }
    }
  }

  grouping testframe-config-data {
    description
      "Grouping with a testframe configuration container.";
    container testframe {
      description
        "Generated traffic burst parameters.";
      leaf type {
        type identityref {
          base ntta:testframe-type;
        }
        default "ntta:unspecified";
        description
          "The 'unspecified' default value enables the option
           for configuration of the testframe type of the traffic
           analyzer outside of the data model specified
           configuration interface.";
      }
      container filter {
        if-feature "testframe-filter";
        presence "When present packets are
                  filtered before analyzed according
                  to the filter type";
        description
          "Contains the filtering rules for processing only
           a specific subset of the frames as test frames.";
        leaf type {
          type identityref {
            base ntta:testframe-filter;
          }
          mandatory true;
          description
            "Type of the applied filter. External modules can
             define alternative filter type identities.";
        }
      }
    }
  }

  augment "/if:interfaces/if:interface" {
    description
      "Traffic analyzer augmentations of ietf-interfaces.";
    container traffic-analyzer {
      presence "Enables the traffic analyzer.";
      description
        "Traffic analyzer top container.";
      uses testframe-config-data;
      uses capture-config-data;
      container state {
        config false;
        description
          "State data.";
        uses statistics-data;
        uses capture-data;
      }
    }
  }

  augment "/if:interfaces/if:interface/ntta:traffic-analyzer/"
        + "ntta:testframe/ntta:filter" {
    when "derived-from-or-self(ntta:type, 'ntta:bit-field-match')";
    description
      "Logical AND of masked bit fields.";
    leaf mask {
      type binary;
      mandatory true;
      description
        "Specifies bit field mask for comparison.
         Non-masked bit fields are ignored.";
    }
    leaf data {
      type binary;
      mandatory true;
      description
        "Specify data to be matched according to the specified mask.";
    }
    leaf offset {
      type uint32;
      mandatory true;
      description
        "Offset in the frame where 'mask' and 'data' are applied.";
    }
  }
}
