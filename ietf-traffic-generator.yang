module ietf-traffic-generator {
  yang-version 1.1;
  namespace "urn:ietf:params:xml:ns:yang:ietf-traffic-generator";
  prefix nttg;

  import ietf-interfaces {
    prefix if;
    reference
      "RFC 8343: A YANG Data Model for Interface Management";
  }
  import ietf-yang-types {
    prefix yang;
    reference
      "RFC 9911: Common YANG Data Types";
  }

  organization
    "IETF Benchmarking Methodology Working Group";
  contact
    "WG Web:   <https://datatracker.ietf.org/group/bmwg/about/>
     WG List:  BMWG <mailto:bmwg@ietf.org>

     Author:   Vladimir Vassilev
               <mailto:vladimir@lightside-instruments.com>";
  description
    "This module contains a collection of YANG definitions for
     management of the traffic generator functionality part
     of network interconnect testers.

     Copyright (c) 2026 IETF Trust and the persons identified as
     authors of the code.  All rights reserved.

     Redistribution and use in source and binary forms, with or
     without modification, is permitted pursuant to, and subject to
     the license terms contained in, the Revised BSD License set
     forth in Section 4.c of the IETF Trust's Legal Provisions
     Relating to IETF Documents
     (https://trustee.ietf.org/license-info).

     All revisions of IETF and IANA published modules can be found
     at the YANG Parameters registry group
     (https://www.iana.org/assignments/yang-parameters).

     This version of this YANG module is part of RFC XXXX; see
     the RFC itself for full legal notices.";

  revision 2026-07-02 {
    description
      "Initial revision.";
    reference
      "RFC XXXX: A YANG Data Model for
                 Network Tester Management";
  }

  feature multi-stream {
    description
      "The device can generate multi-stream traffic.";
  }

  feature realtime-epoch {
    description
      "The device can generate traffic precisely
       at configured realtime epoch.";
  }

  identity testframe-type {
    description
      "Base identity for all test frame types.";
  }

  identity static {
    base testframe-type;
    description
      "Indicates static test frame.
       The frame data and size are constant.";
  }

  identity dynamic {
    base testframe-type;
    description
      "Base identity for dynamic test frame.

       When used itself, it identifies unspecified
       dynamic test frame type configured outside
       of the data model specified configuration
       interface.";
  }

  identity modifier-action-type {
    description
      "Base identity for all modifier action types.";
  }

  identity increment {
    base modifier-action-type;
    description
      "Indicates increment modifier action.
       The operation is performed in network byte order.";
  }

  identity decrement {
    base modifier-action-type;
    description
      "Indicates decrement modifier action.
       The operation is performed in network byte order.";
  }

  identity random {
    base modifier-action-type;
    description
      "Indicates implementation-specific random modifier action.";
  }

  grouping common-data {
    description
      "Common configuration data.";
    leaf realtime-epoch {
      if-feature "realtime-epoch";
      type yang:date-and-time;
      description
        "If this leaf is present the stream generation will start
         at the specified realtime epoch.";
    }
    leaf start-delay {
      type uint64;
      units "octets";
      description
        "If this leaf is present, the traffic generation will start
         after the specified number of idle octets have elapsed.";
    }
    leaf total-frames {
      type uint64;
      description
        "If this leaf is present the traffic generation will stop
         after the specified number of frames are generated.";
    }
  }

  grouping burst-data {
    description
      "Generated traffic burst parameters.";
    leaf testframe-type {
      type identityref {
        base nttg:testframe-type;
      }
      default "nttg:static";
      description
        "In case of dynamic test frames this leaf
         can specify a derived dynamic test frame identity.
         For static test frames there is no practical use
         of derived identities.";
    }
    leaf frame-size {
      type uint32;
      units "octets";
      mandatory true;
      description
        "Size of the frames generated. For example, for
         Ethernet interfaces the following definition
         applies:

         Ethernet frame-size, in octets, includes:
         * Destination Address (6 octets),
         * Source Address (6 octets),
         * Frame Type (2 octets),
         * Data (min 46 octets or 42 octets + 4 octets 802.1Q tag),
         * Frame Check Sequence (FCS) (4 octets)

         Ethernet frame-size does not include:
         * Preamble (dependent on MAC configuration
                    by default 7 octets),
         * Start of frame delimiter (1 octet)

         Minimum standard Ethernet frame-size is 64 bytes but
         generators might support smaller sizes for validation.";
    }
    leaf frame-data {
      type binary;
      description
        "The raw frame data.
         The length of the specified data can be
         shorter, then the '../frame-size' value
         specifying only the header of the frame.

         If the data specified is shorter, then the
         missing tail is filled with data generated by
         the algorithm corresponding to the
         '../testframe-type' for the corresponding
         dynamic fields or filled with zeros.

         In the case of an Ethernet interface and static
         test frame the correct 4-octet FCS is added to
         the generated frames. The only way to generate
         frames with bad FCS is to specify the data
         of full 'frame-size' length with its last 4 octets
         containing bad FCS value.

         If the frame data specified is longer,
         then '../frame-size' the excess of the
         specified frame data is truncated.

         In multi-stream mode, if 'frame-data' leaf for one of the
         streams is not specified, it is the value specified for
         the closest stream that precedes it that is used.";
    }
    leaf gap {
      type uint64;
      units "octets";
      mandatory true;
      description
        "Length of the period between generated frames.
         For example, for Ethernet interfaces the following
         definition applies:

         The gap between transmission of frames is the sum
         of the minimum interframe gap (IFG) as defined in
         IEEE 802.3 plus any additional idle octets plus
         the preamble (7 octets) and the start of frame
         delimiter (1 octet). A brief recovery time
         between frames allows devices to prepare for
         reception of the next frame. The minimum
         interframe gap is 96-bit times (12-octet times) (the time it
         takes to transmit 96-bits (12 octets) of raw data on the
         medium). However, the preamble (7 octets) and start of
         frame delimiter (1 octet) are considered a constant gap that
         should be included in the gap. Thus, the minimum
         value for standard Ethernet transmission should be considered
         20 octets.";
    }
    leaf burst-gap {
      type uint32;
      units "octets";
      description
        "Is similar to the gap but takes place between
         any two bursts of the stream.";
    }
    leaf frames-per-burst {
      type uint32;
      description
        "Indicates number of frames contained in a burst.";
    }
  }

  grouping modifier-data {
    description
      "Frame data modification parameters.";
    container modifiers {
      description
        "Container holding the configured modifiers list.";
      list modifier {
        key "id";
        description
          "Each modifier specifies the action to be performed
           on data at a certain offset.

           Overlapping modifiers have no ordering rules
           and the behavior will be unspecified.";
        leaf id {
          type uint32;
          description
            "Number specifying the identifier of the modifier.";
        }
        leaf action {
          type identityref {
            base nttg:modifier-action-type;
          }
          mandatory true;
          description
            "Modifier action type.";
        }
        leaf offset {
          type uint32;
          units "octets";
          mandatory true;
          description
            "Offset of the modified data of the frame.";
        }
        leaf mask {
          type binary;
          mandatory true;
          description
            "Bit mask of the actual bits affected by the modifier.";
        }
        leaf repetitions {
          type uint32;
          mandatory true;
          description
            "Count of the packets that will repeat the data before
             the modifier makes the next update.";
        }
      }
    }
  }

  grouping multi-stream-data {
    description
      "Multi stream traffic generation parameters.";
    container streams {
      description
        "A container holding the stream list.";
      list stream {
        key "id";
        description
          "Each stream repeats a burst until frames-per-stream
           count is reached followed by stream-gap delay.";
        leaf id {
          type uint32;
          description
            "Number specifying the order of the stream.";
        }
        uses burst-data;
        leaf frames-per-stream {
          type uint64;
          mandatory true;
          description
            "The count of frames to be generated before
             generation of the next stream is started.";
        }
        leaf stream-gap {
          type uint64;
          units "octets";
          mandatory true;
          description
            "Idle period after the last frame of the last burst.";
        }
        uses modifier-data;
      }
    }
  }

  augment "/if:interfaces/if:interface" {
    description
      "Traffic generator augmentations of 'ietf-interfaces'.";
    container traffic-generator {
      presence "Enables the traffic generator.";
      description
        "Traffic generator data.";
      choice type {
        mandatory true;
        description
          "Choice of the type of the generator:
           Single or multi stream.";
        case single-stream {
          uses burst-data;
          uses modifier-data;
        }
        case multi-stream {
          if-feature "multi-stream";
          uses multi-stream-data;
        }
      }
      uses common-data;
    }
  }
}
